module vyatta-routing-instance-interfaces-v1 {
        namespace "urn:vyatta.com:mgmt:vyatta-routing-instance-interfaces-v1:1";
        prefix vyatta-routing-instance-if-v1;

	import configd-v1 { prefix configd; }
	import vyatta-routing-v1 { prefix vyatta-routing; }
	import vyatta-types-v1 {
		prefix types;
	}

	organization "AT&T Inc.";
	contact
		"AT&T
		 Postal: 208 S. Akard Street
		         Dallas, TX 25202
		 Web: www.att.com";

	description
		"Copyright (c) 2017-2019, AT&T Intellectual Property.
		 All rights reserved.

		 Copyright (c) 2016 by Brocade Communications Systems, Inc.
		 All rights reserved.

		 Redistribution and use in source and binary forms, with or without
		 modification, are permitted provided that the following conditions
		 are met:

		   1. Redistributions of source code must retain the above copyright
		      notice, this list of conditions and the following disclaimer.
		   2. Redistributions in binary form must reproduce the above
		      copyright notice, this list of conditions and the following
		      disclaimer in the documentation and/or other materials provided
		      with the distribution.
		   3. Neither the name of the copyright holder nor the names of its
		      contributors may be used to endorse or promote products derived
		      from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-routing-instance-interfaces-v1";

	revision 2019-05-02 {
		description "Changed double quotes to single quotes to facilitate pyang upgrade";
	}

	revision 2018-08-22 {
		description "Removed validation script";
	}

	revision 2017-11-03 {
		description
			"Make suggestions appear on routing instance
			interfaces list. This is an internal-only
			change and there are no semantic changes to
			external users of the yang file so this is a
			no-op for that purpose.
			Do not suggest lo/lord interfaces.";
	}

	revision 2016-08-12 {
		description "Add warning for undefined interfaces.";
	}

	revision 2016-04-11 {
		description "Initial revision of version 1.";
	}

	augment /vyatta-routing:routing {
		configd:begin "/opt/vyatta/sbin/vrf-bind-interface --all --verify";
	}

	augment /vyatta-routing:routing/vyatta-routing:routing-instance {
		list interface {
			description "List of interfaces to bind with this routing instance";
			configd:help "Bind interface to routing instance";
			configd:allowed '/opt/vyatta/sbin/vyatta-interfaces.pl --show all --filter-out ^lo$\|^lord';
			key "name";
			leaf "name" {
				type types:interface-ifname;

				must "not(current() = 'lo') and " +
					"(not(starts-with(current(),'lord')))" {
					error-message "Loopback interface name lo or name starts with lord cannot be bound to routing instances.";
				}
				must "(1 = count(../../../vyatta-routing:routing-instance/interface[name = current()]))" {
					error-message "Interface cannot be bound to multiple routing instances";
				}
			}
		}
	}
}
